module data-export-import-akka-info-provider-cfg {
    yang-version 1;
    namespace "urn:opendaylight:daexim:akka-info-provider";
    prefix "cfg";

    import config { prefix config; revision-date 2013-04-05; }
    import data-export-import-spi { prefix spi; revision-date 2016-08-16; }
    import actor-system-provider-service { prefix asp; revision-date 2015-10-05; }

    organization
        "Brocade BSC Team";

    contact
        "Richard Kosegi <mailto:rkosegi@brocade.com>";

    description
        "This module contains YANG definitions for daexim application
        AKKA info provider configuration";

    revision "2016-08-16" {
        description "Initial revision.";
    }
    identity akka-nodename-provider-impl {
        base config:module-type;
        config:provided-service spi:node-name-provider;
        config:java-name-prefix AkkaNodeNameProvider;
    }

    augment "/config:modules/config:module/config:configuration" {
        case akka-nodename-provider-impl {
            when "/config:modules/config:module/config:type = 'akka-nodename-provider-impl'";
            container actor-system-provider-service {
                uses config:service-ref {
                    refine type {
                        mandatory true;
                        config:required-identity asp:actor-system-provider-service;
                    }
                }
            }
        }
    }
}
