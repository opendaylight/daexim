module A {
    namespace "testA";
    prefix "A";
    organization "Brocade BSC Team";
    contact "Richard Kosegi <mailto:rkosegi@brocade.com>";
    description
      "Test model #1

       Copyright (c) 2016 Brocade Communications Systems, Inc. All rights reserved.

       This program and the accompanying materials are made available
       under the terms of the Eclipse Public License v1.0 which
       accompanies this distribution, and is available at
       http://www.eclipse.org/legal/epl-v10.html";

    revision "2016-09-13" {
        description "Initial version";
    }

    container data1 {
        leaf leaf1 {
            type string;
        }
    }
}
