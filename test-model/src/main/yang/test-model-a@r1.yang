module A {
    namespace "testA";
    prefix "A";
    organization "Brocade BSC Team";
    contact "Richard Kosegi <mailto:rkosegi@brocade.com>";
    description "Test model #1";
    revision "2016-09-13" {
        description "Initial version";
    }

    container data1 {
        leaf leaf1 {
            type string;
        }
    }
}
